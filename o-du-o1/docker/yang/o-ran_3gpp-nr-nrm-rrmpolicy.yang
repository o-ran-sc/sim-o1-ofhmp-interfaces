module o-ran_3gpp-nr-nrm-rrmpolicy {
  yang-version 1.1;
  namespace "urn:o-ran:oran-rrmpolicy";
  prefix "or-rrmpolicy";

  import _3gpp-nr-nrm-rrmpolicy {
    prefix "nrrrmpolicy3gpp";
  }
  
  organization "O-RAN Alliance";

  contact
    "www.o-ran.org";

  description
    "This module defines the augmentation of the SA5 yang data model
     according to 28.541 to split the resourceType PRB type into two
     types: ul-prb and dl-prb.

     Copyright 2021 the O-RAN Alliance.

     THIS SOFTWARE IS PROVIDED BY THE COPYRIGHT HOLDERS AND
     CONTRIBUTORS 'AS IS' AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING,
     BUT NOT LIMITED TO, PROCUREMENT OF SUBSTITUTE GOODS OR
     SERVICES; LOSS OF USE, DATA, OR PROFITS; OR BUSINESS
     INTERRUPTION) HOWEVER CAUSED AND ON ANY THEORY OF LIABILITY,
     WHETHER IN CONTRACT, STRICT LIABILITY, OR TORT (INCLUDING
     NEGLIGENCE OR OTHERWISE) ARISING IN ANY WAY OUT OF THE USE OF
     THIS SOFTWARE, EVEN IF ADVISED OF THE POSSIBILITY OF SUCH DAMAGE.

     Redistribution and use in source and binary forms, with or
     without modification, are permitted provided that the following
     conditions are met:

     * Redistributions of source code must retain the above
       copyright notice, this list of conditions and the above
       disclaimer.
     * Redistributions in binary form must reproduce the above
       copyright notice, this list of conditions and the above
       disclaimer in the documentation and/or other materials
       provided with the distribution.
     * Neither the Members of the O-RAN Alliance nor the names of
       its contributors may be used to endorse or promote products
       derived from this software without specific prior written
       permission.";

  revision 2021-10-31 {
    description
      "Revision that depcrecates the 'direction' leaf.";
    reference
      "O1 for O-DU v03.00 Chapter 10.5.";
  }
  
  revision 2021-06-24 {
    description
      "Initial version";
    reference
      "ORAN-WG5.MP.O1.0-v01.00";
  }

  augment "/nrrrmpolicy3gpp:RRMPolicyRatio/nrrrmpolicy3gpp:attributes" {
    when "(nrrrmpolicy3gpp:resourceType = 'PRB')";
    container o-ran-rrmpolicy {
      leaf direction {
        type enumeration {
          enum dl {
            description
              "Downlink Physical Resource Blocks.";
          }
          enum ul {
            description
              "Uplink Physical Resource Blocks.";
          }
          enum both {
            description
              "When Physical Resource Blocks (PRB) are allocated for
               both uplink and downlink. This flag makes the model
               backward compatible with existing implementations
               that do not want to split the resources.";
          }
        }
	status deprecated;
	description
	  "Specifies the direction for the PRBs.";
      }
      description
	"Container for RRMPolicy_ IOC attributes.";
    }
    description
      "Augment of the 3GPP RRMPolicy_ IOC.";
  }
}
