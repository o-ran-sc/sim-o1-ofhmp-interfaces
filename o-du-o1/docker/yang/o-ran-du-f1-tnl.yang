module o-ran-du-f1-tnl{
  yang-version 1.1;
  namespace "urn:o-ran:du-f1-tnl:1.0";
  prefix "o-ran-du-f1-tnl";
  import _3gpp-common-managed-element {
    prefix "me3gpp";
  }

  import _3gpp-nr-nrm-gnbdufunction {
    prefix "gnbdu3gpp";
  }

  import _3gpp-nr-nrm-ep {
    prefix "ep3gpp";
    // TODO AS removed revision date
    // revision-date 2020-03-02;
  }
  
  import ietf-hardware {
    prefix hw;
  }
  
  import o-ran-hardware {
    prefix o-ran-hw;
    // TODO AS removed revision date
    // revision-date "2020-04-17";
  }
  
  import o-ran-u-plane-tnl {
    prefix "o-ran-u-tnl";
    revision-date "2020-09-25";
  }
  
  import o-ran-c-plane-tnl {
    prefix "o-ran-c-tnl";
    revision-date "2020-09-25";
  }  
  organization 
  "O-RAN Alliance";

contact
  "www.o-ran.org";

description 
  "This module augments TNL for DU F1 end-point in 3GPP SA5 data models.

   Copyright 2020 the O-RAN Alliance.

   THIS SOFTWARE IS PROVIDED BY THE COPYRIGHT HOLDERS AND CONTRIBUTORS 'AS IS'
   AND ANY EXPRESS OR IMPLIED WARRANTIES, INCLUDING, BUT NOT LIMITED TO, THE
   IMPLIED WARRANTIES OF MERCHANTABILITY AND FITNESS FOR A PARTICULAR PURPOSE
   ARE DISCLAIMED. IN NO EVENT SHALL THE COPYRIGHT HOLDER OR CONTRIBUTORS BE
   LIABLE FOR ANY DIRECT, INDIRECT, INCIDENTAL, SPECIAL, EXEMPLARY, OR
   CONSEQUENTIAL DAMAGES (INCLUDING, BUT NOT LIMITED TO, PROCUREMENT OF
   SUBSTITUTE GOODS OR SERVICES; LOSS OF USE, DATA, OR PROFITS; OR BUSINESS
   INTERRUPTION) HOWEVER CAUSED AND ON ANY THEORY OF LIABILITY, WHETHER IN
   CONTRACT, STRICT LIABILITY, OR TORT (INCLUDING NEGLIGENCE OR OTHERWISE)
   ARISING IN ANY WAY OUT OF THE USE OF THIS SOFTWARE, EVEN IF ADVISED OF THE
   POSSIBILITY OF SUCH DAMAGE.

   Redistribution and use in source and binary forms, with or without
   modification, are permitted provided that the following conditions are met:

   * Redistributions of source code must retain the above copyright notice,
     this list of conditions and the above disclaimer.
   * Redistributions in binary form must reproduce the above copyright notice,
     this list of conditions and the above disclaimer in the documentation
     and/or other materials provided with the distribution.
   * Neither the Members of the o-RAN Alliance nor the names of its
     contributors may be used to endorse or promote products derived from
     this software without specific prior written permission.";

  revision "2020-09-25" {
    description
      "version 1.0.0 - first release of O-RAN O1 for O-DU YANG models";

    reference "ORAN-WG5.MP.0-v01.00";
  }
    
  augment "/me3gpp:ManagedElement/gnbdu3gpp:GNBDUFunction/ep3gpp:EP_F1U/ep3gpp:attributes" {
    when "(derived-from-or-self(/hw:hardware/hw:component/hw:class, 'o-ran-hw:O-DU-COMPONENT'))";
    container o-ran-u-plane-tnl-additional-config {
      description "Container for U-plane F1 TNL configuration";
      uses o-ran-u-tnl:gtp-configuration;
      uses o-ran-u-tnl:dscp-marking;    
    }
    description "SA5 gNB DU function augmented with additional F1 TNL configuration";    
  }
  
  augment "/me3gpp:ManagedElement/gnbdu3gpp:GNBDUFunction/ep3gpp:EP_F1C/ep3gpp:attributes" {
    when "(derived-from-or-self(/hw:hardware/hw:component/hw:class, 'o-ran-hw:O-DU-COMPONENT'))";
    container o-ran-c-plane-tnl-additional-config {
      description "Container for C-plane F1 TNL configuration";
      uses o-ran-c-tnl:sctp-configuration;
      uses o-ran-c-tnl:dscp-marking;    
    }
    description "SA5 gNB DU function augmented with additional F1 TNL configuration";
  }
}
